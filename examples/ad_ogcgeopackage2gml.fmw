FME workspace ad_ogcgeopackage2gml.fmw

Parameters:
- SourceDataset_OGCGEOPACKAGE =

Readers:
- OGCGEOPACKAGE_1: OGCGEOPACKAGE from $(SourceDataset_OGCGEOPACKAGE) in EPSG:25832

Sampler_2
    RATE = 10
    SAMPLE_MODE = No
    SAMPLE_TYPE_LONG = Every Nth Feature
    SAMPLED -> AttributeCopier_4
AttributeCopier_4
    ATTR_TABLE = COPY inspireid > gmlid
    MISSING_INPUT_ATTRS = REMOVE
    -> Postaldescriptor_GPKG2GML
Sampler_3
    RATE = 100
    SAMPLE_MODE = No
    SAMPLE_TYPE_LONG = Every Nth Feature
    SAMPLED -> AttributeCopier_3
AttributeCopier_3
    ATTR_TABLE = COPY inspireid > gmlid
    MISSING_INPUT_ATTRS = REMOVE
    -> Addressareaname_GPKG2GML
AttributeCopier_2
    ATTR_TABLE = COPY inspireid > gmlid
    MISSING_INPUT_ATTRS = REMOVE
    -> Adminunitname_GPKG2GML
Sampler
    RATE = 10000
    SAMPLE_MODE = No
    SAMPLE_TYPE_LONG = Every Nth Feature
    SAMPLED -> GeometryExtractor_2
GeometryExtractor_2
    ATTR = gml_location
    KIND_LONG = GML v3.2.1
    OGCVERSION = 1.2
    OGC_WKT_PRECISION_DISPLAY = 64-bit
    OGEOSMS_URL_PREFIX = http://maps.google.com/?q=
    OMIT_NAMESPACES_DISPLAY = No
    PREFER_POLYGON_OVER_SURFACE = No
    REMOVE_GEOMETRY = No
    SRS_AXIS_ORDER_DISPLAY = 1,2
    SRS_NAME = http://www.opengis.net/def/crs/EPSG/0/25832
    -> AttributeCopier
AttributeCopier
    ATTR_TABLE = COPY inspireid > gmlid
    MISSING_INPUT_ATTRS = REMOVE
    -> Address_GPKG2GML
Sampler_4
    RATE = 1000
    SAMPLE_MODE = No
    SAMPLE_TYPE_LONG = Every Nth Feature
    SAMPLED -> AttributeCopier_5
AttributeCopier_5
    ATTR_TABLE = COPY inspireid > gmlid
    MISSING_INPUT_ATTRS = REMOVE
    -> Thoroughfarename_GPKG2GML
FeatureWriter
    COORDSYS = EPSG:25832
    DATASET = C:\path\to\gml.gml
    DATASET_ATTR = _dataset
    FEATURE_TYPE_LIST_ATTR = _feature_types
    FORMAT = INSPIRE
    INSPIRE_ADD_NAMESPACE_PREFIX_TO_NAMES = FEATURE_TYPES
    INSPIRE_COORDINATE_SYSTEM_GRANULARITY = DATASET
    INSPIRE_DESTINATION_DATASETTYPE_VALIDATION = Yes
    INSPIRE_FEATURE_COLLECTION = FeatureCollection
    INSPIRE_FEATURE_COLLECTION_NS_URI = http://www.opengis.net/gml/3.2
    INSPIRE_GENERATE_GEOMETRY_IDS = NO
    INSPIRE_GUESS_GEOMETRY_NAMES = YES
    INSPIRE_INDENT_SIZE = 1
    INSPIRE_MAP_ALL_SUBSTITUTABLE_PROPERTIES = YES
    INSPIRE_MAP_COMPLEX_PROPERTIES_AS = Nested Attributes
    INSPIRE_MAP_COVERAGES_AS_FEATURE_TYPES = NO
    INSPIRE_MAP_EMBEDDED_OBJECTS_AS = ATTRIBUTES
    INSPIRE_MAP_PREDEFINED_GML_PROPERTIES = YES
    INSPIRE_OUTPUT_ENCODING = utf-8
    INSPIRE_PRETTY_PRINT = Yes
    INSPIRE_PROFILE = GENERIC_APPLICATION_SCHEMA
    INSPIRE_REPLACE_TABS_WITH_SPACES = No
    INSPIRE_SELECT_THEMES = by Themes
    INSPIRE_SRS_AXIS_ORDER = 1,2
    INSPIRE_SRS_NAME = http://www.opengis.net/def/crs/EPSG/0/25832
    INSPIRE_SUPPRESS_XSI_SCHEMALOCATION = NO
    INSPIRE_TARGET_XSI_SCHEMALOCATION_URL = http://www.opengis.net/gml/3.2 http://schemas.opengis.net/gml/3.2.1/gml.xsd http://inspire.ec.europa.eu/schemas/ad/4.0 http://inspire.ec.europa.eu/schemas/ad/4.0/Addresses.xsd
    INSPIRE_VALIDATE_OUTPUT_DATASET = YES
    INSPIRE_XSD_NAMESPACE_URI = http://inspire.ec.europa.eu/schemas/ad/4.0
    TOTAL_FEATURES_WRITTEN_ATTR = _total_features_written
    SUMMARY -> FeatureWriter_Summary
FeatureWriter_Summary: Inspector

Bookmark: Geopackage tables
postaldescriptor (reader OGCGEOPACKAGE_1)
    attributes: postname text, postcode text, validto datetime, inspireid text, alternativeidentifier text, beginlifespanversion datetime, endlifespanversion datetime, status text, validfrom datetime, situatedwithin_addressareaname text, situatedwithin_adminunitname text, situatedwithin_postaldescriptor text, situatedwithin_thoroughfarename text
    -> Sampler_2
addressareaname (reader OGCGEOPACKAGE_1)
    attributes: name text, validto datetime, inspireid text, alternativeidentifier text, beginlifespanversion datetime, endlifespanversion datetime, status text, validfrom datetime, situatedwithin_addressareaname text, situatedwithin_adminunitname text, situatedwithin_postaldescriptor text, situatedwithin_thoroughfarename text, namedplace text
    -> Sampler_3
adminunitname (reader OGCGEOPACKAGE_1)
    attributes: validto datetime, inspireid text, alternativeidentifier text, beginlifespanversion datetime, endlifespanversion datetime, status text, validfrom datetime, name text, level text, situatedwithin_addressareaname text, situatedwithin_adminunitname text, situatedwithin_postaldescriptor text, situatedwithin_thoroughfarename text, adminunit text
    -> AttributeCopier_2
address (reader OGCGEOPACKAGE_1)
    attributes: inspireid text, alternativeidentifier text, position_default text, position_method text, position_specification text, status text, locator_designator_1_designator text, locator_designator_1_type text, locator_designator_2_designator text, locator_designator_2_type text, locator_designator_3_designator text, locator_designator_3_type text, locator_level text, locator_name_name text, locator_name_type text, locator_withinscopeof_addressareaname text, locator_withinscopeof_adminunitname text, locator_withinscopeof_postaldescriptor text, locator_withinscopeof_thoroughfarename text, validfrom datetime, validto datetime, beginlifespanversion datetime, endlifespanversion datetime, component_addressareaname_1 text, component_addressareaname_2 text, component_addressareaname_3 text, component_adminunitname_1 text, component_adminunitname_2 text, component_adminunitname_3 text, component_adminunitname_4 text,
      component_adminunitname_5 text, component_adminunitname_6 text, component_postaldescriptor text, component_thoroughfarename text, parentaddress text, parcel text, building text
    -> Sampler
thoroughfarename (reader OGCGEOPACKAGE_1)
    attributes: validto datetime, inspireid text, alternativeidentifier text, beginlifespanversion datetime, endlifespanversion datetime, status text, validfrom datetime, name_name text, name_nameparts_part text, name_nameparts_type text, situatedwithin_addressareaname text, situatedwithin_adminunitname text, situatedwithin_postaldescriptor text, situatedwithin_thoroughfarename text, transportlink text
    -> Sampler_4

Bookmark: Transformation GPKG->GML
Postaldescriptor_GPKG2GML: AttributeManager
    ATTR_TABLE:
      RENAME_SET_VALUE postname > postName{0}.GeographicalName.spelling{0}.SpellingOfName.text
      SET_TO postName{0}.GeographicalName.spelling{0}.SpellingOfName.script = Latn
      SET_TO postName{0}.GeographicalName.language = dan
      RENAME_SET_VALUE postcode > postCode
      RENAME_SET_VALUE validto > validTo = @DateTimeFormat(@Value(validTo), ISO)
      RENAME_SET_VALUE inspireid > inspireId.Identifier.localId = @TrimLeft(@Value(inspireId.Identifier.localId),https://geo.data.gov.dk/dataset/)
      SET_TO inspireId.Identifier.namespace = https://geo.data.gov.dk/dataset/50b921ea-935e-d605-2287-4ee364046795
      RENAME_SET_VALUE alternativeidentifier > alternativeIdentifier.xsi_nil = true
      SET_TO alternativeIdentifier.nilReason = other:unpopulated
      RENAME_SET_VALUE beginlifespanversion > beginLifespanVersion = @DateTimeFormat(@Value(beginLifespanVersion), ISO)
      RENAME_SET_VALUE endlifespanversion > endLifespanVersion = @DateTimeFormat(@Value(endLifespanVersion), ISO)
      RENAME_SET_VALUE status > status.nilReason = other:unpopulated
      SET_TO status.xsi_nil = true
      RENAME_SET_VALUE validfrom > validFrom = @DateTimeFormat(@Value(validFrom), ISO)
      RENAME_SET_VALUE situatedwithin_addressareaname > situatedWithin{3}.nilReason = other:unpopulated
      SET_TO situatedWithin{3}.xsi_nil = true
      RENAME_SET_VALUE situatedwithin_adminunitname > situatedWithin{2}.nilReason = other:unpopulated
      SET_TO situatedWithin{2}.xsi_nil = true
      RENAME_SET_VALUE situatedwithin_postaldescriptor > situatedWithin{1}.nilReason = other:unpopulated
      SET_TO situatedWithin{1}.xsi_nil = true
      RENAME_SET_VALUE situatedwithin_thoroughfarename > situatedWithin{0}.xlink_href
      RENAME_SET_VALUE gmlid > gmlid_a = @Trim(@Value(gmlid_a),https://geo.data.gov.dk/dataset)
      RENAME_SET_VALUE gmlid_a > gml:id = _@ReplaceString(@Value(gml:id),/,_)
    -> FeatureWriter [Output]
Addressareaname_GPKG2GML: AttributeManager
    ATTR_TABLE:
      RENAME_SET_VALUE name > name{0}.GeographicalName.spelling{0}.SpellingOfName.text
      SET_TO name{0}.GeographicalName.spelling{0}.SpellingOfName.script = Latn
      SET_TO name{0}.GeographicalName.language = dan
      RENAME_SET_VALUE validto > validTo = @DateTimeFormat(@Value(validTo), ISO)
      RENAME_SET_VALUE inspireid > inspireId.Identifier.localId = @TrimLeft(@Value(inspireId.Identifier.localId),https://geo.data.gov.dk/dataset/)
      SET_TO inspireId.Identifier.namespace = https://geo.data.gov.dk/dataset/50b921ea-935e-d605-2287-4ee364046795
      RENAME_SET_VALUE alternativeidentifier > alternativeIdentifier.xsi_nil = true
      SET_TO alternativeIdentifier.nilReason = other:unpopulated
      RENAME_SET_VALUE beginlifespanversion > beginLifespanVersion = @DateTimeFormat(@Value(beginLifespanVersion), ISO)
      RENAME_SET_VALUE endlifespanversion > endLifespanVersion = @DateTimeFormat(@Value(endLifespanVersion), ISO)
      RENAME_SET_VALUE status > status.xlink_href
      RENAME_SET_VALUE validfrom > validFrom = @DateTimeFormat(@Value(validFrom), ISO)
      RENAME_SET_VALUE situatedwithin_addressareaname > situatedWithin{3}.xsi_nil = true
      SET_TO situatedWithin{3}.nilReason = other:unpopulated
      RENAME_SET_VALUE situatedwithin_adminunitname > situatedWithin{0}.xlink_href
      RENAME_SET_VALUE situatedwithin_postaldescriptor > situatedWithin{1}.xsi_nil = true
      SET_TO situatedWithin{1}.nilReason = other:unpopulated
      RENAME_SET_VALUE situatedwithin_thoroughfarename > situatedWithin{2}.xsi_nil = true
      SET_TO situatedWithin{2}.nilReason = other:unpopulated
      RENAME_SET_VALUE namedplace > namedPlace.xsi_nil = true
      RENAME_SET_VALUE gmlid > gmlid_a = @Trim(@Value(gmlid_a),https://geo.data.gov.dk/dataset)
      RENAME_SET_VALUE gmlid_a > gml:id = _@ReplaceString(@Value(gml:id),/,_)
    -> FeatureWriter [Output00]
Adminunitname_GPKG2GML: AttributeManager
    ATTR_TABLE:
      RENAME_SET_VALUE validto > validTo = @DateTimeFormat(@Value(validTo), ISO)
      RENAME_SET_VALUE inspireid > inspireId.Identifier.localId = @TrimLeft(@Value(inspireId.Identifier.localId),https://geo.data.gov.dk/dataset/)
      SET_TO inspireId.Identifier.namespace = https://geo.data.gov.dk/dataset/50b921ea-935e-d605-2287-4ee364046795
      RENAME_SET_VALUE alternativeidentifier > alternativeIdentifier.xsi_nil = true
      SET_TO alternativeIdentifier.nilReason = other:unpopulated
      RENAME_SET_VALUE beginlifespanversion > beginLifespanVersion = @DateTimeFormat(@Value(beginLifespanVersion), ISO)
      RENAME_SET_VALUE endlifespanversion > endLifespanVersion = @DateTimeFormat(@Value(endLifespanVersion), ISO)
      RENAME_SET_VALUE status > status.xsi_nil = true
      SET_TO status.nilReason = other:unpopulated
      RENAME_SET_VALUE validfrom > validFrom = @DateTimeFormat(@Value(validFrom), ISO)
      RENAME_SET_VALUE name > name{0}.GeographicalName.spelling{0}.SpellingOfName.text
      SET_TO name{0}.GeographicalName.spelling{0}.SpellingOfName.script = Latn
      SET_TO name{0}.GeographicalName.language = dan
      RENAME_SET_VALUE level > level.xlink_href
      RENAME_SET_VALUE situatedwithin_addressareaname > situatedWithin{0}.xsi_nil = true
      SET_TO situatedWithin{0}.nilReason = other:unpopulated
      RENAME_SET_VALUE situatedwithin_adminunitname > situatedWithin{1}.xsi_nil = true
      SET_TO situatedWithin{1}.nilReason = other:unpopulated
      RENAME_SET_VALUE situatedwithin_postaldescriptor > situatedWithin{2}.xsi_nil = true
      SET_TO situatedWithin{2}.nilReason = other:unpopulated
      RENAME_SET_VALUE situatedwithin_thoroughfarename > situatedWithin{3}.xsi_nil = true
      SET_TO situatedWithin{3}.nilReason = other:unpopulated
      RENAME_SET_VALUE adminunit > adminUnit.xsi_nil = true
      SET_TO adminUnit.nilReason = other:unpopulated
      RENAME_SET_VALUE gmlid > gmlid_a = @Trim(@Value(gmlid_a),https://geo.data.gov.dk/dataset)
      RENAME_SET_VALUE gmlid_a > gml:id = _@ReplaceString(@Value(gml:id),/,_)
    -> FeatureWriter [Output01]
Address_GPKG2GML: AttributeManager
    ATTR_TABLE:
      RENAME_SET_VALUE inspireid > inspireId.Identifier.localId = @TrimLeft(@Value(inspireId.Identifier.localId),https://geo.data.gov.dk/dataset/)
      SET_TO inspireId.Identifier.namespace = https://geo.data.gov.dk/dataset/50b921ea-935e-d605-2287-4ee364046795
      RENAME_SET_VALUE alternativeidentifier > alternativeIdentifier.xsi_nil = true
      SET_TO alternativeIdentifier.nilReason = other:unpopulated
      RENAME_SET_VALUE position_default > position{0}.GeographicPosition.default
      RENAME_SET_VALUE position_method > position{0}.GeographicPosition.method.xlink_href
      RENAME_SET_VALUE position_specification > position{0}.GeographicPosition.specification.xlink_href
      RENAME_SET_VALUE status > status.xlink_href
      RENAME_SET_VALUE validfrom > validFrom = @DateTimeFormat(@Value(validFrom), ISO)
      RENAME_SET_VALUE validto > validTo = @DateTimeFormat(@Value(validTo), ISO)
      RENAME_SET_VALUE beginlifespanversion > beginLifespanVersion = @DateTimeFormat(@Value(beginLifespanVersion), ISO)
      RENAME_SET_VALUE endlifespanversion > endLifespanVersion = @DateTimeFormat(@Value(endLifespanVersion), ISO)
      RENAME_SET_VALUE component_adminunitname_1 > component_adminunitname_1a = @Trim(@Value(component_adminunitname_1a),https://geo.data.gov.dk/dataset)
      RENAME_SET_VALUE component_adminunitname_1a > component_adminunitname_1b = @ReplaceString(@Value(component_adminunitname_1b),/,_)
      RENAME_SET_VALUE component_adminunitname_1b > component_adminunitname_1b_# = #_@Value(component_adminunitname_1b_#)
      RENAME_SET_VALUE component_adminunitname_1b_# > component{0}.xlink_href
      RENAME_SET_VALUE component_postaldescriptor > component_postaldescriptor_a = @Trim(@Value(component_postaldescriptor_a),https://geo.data.gov.dk/dataset)
      RENAME_SET_VALUE component_postaldescriptor_a > component_postaldescriptor_b = @ReplaceString(@Value(component_postaldescriptor_b),/,_)
      RENAME_SET_VALUE component_postaldescriptor_b > component_postaldescriptor_b_# = #_@Value(component_postaldescriptor_b_#)
      RENAME_SET_VALUE component_postaldescriptor_b_# > component{1}.xlink_href
      RENAME_SET_VALUE component_thoroughfarename > component_thoroughfarename_a = @Trim(@Value(component_thoroughfarename_a),https://geo.data.gov.dk/dataset)
      RENAME_SET_VALUE component_thoroughfarename_a > component_thoroughfarename_b = @ReplaceString(@Value(component_thoroughfarename_b),/,_)
      RENAME_SET_VALUE component_thoroughfarename_b > component_thoroughfarename_b_# = #_@Value(component_thoroughfarename_b_#)
      RENAME_SET_VALUE component_thoroughfarename_b_# > component{2}.xlink_href
      RENAME_SET_VALUE component_addressareaname_1 > component_addressareaname_1a = @Trim(@Value(component_addressareaname_1a),https://geo.data.gov.dk/dataset)
      RENAME_SET_VALUE component_addressareaname_1a > component_addressareaname_1b = @ReplaceString(@Value(component_addressareaname_1b),/,_)
      RENAME_SET_VALUE component_addressareaname_1b > component_addressareaname_1b_# = #_@Value(component_addressareaname_1b_#)
      RENAME_SET_VALUE component_addressareaname_1b_# > component{3}.xlink_href
      RENAME_SET_VALUE component_adminunitname_2 > component_adminunitname_2a = @Trim(@Value(component_adminunitname_2a),https://geo.data.gov.dk/dataset)
      RENAME_SET_VALUE component_adminunitname_2a > component_adminunitname_2b = @ReplaceString(@Value(component_adminunitname_2b),/,_)
      RENAME_SET_VALUE component_adminunitname_2b > component_adminunitname_2b_# = #_@Value(component_adminunitname_2b_#)
      RENAME_SET_VALUE component_adminunitname_2b_# > component{4}.xlink_href
      RENAME_SET_VALUE component_adminunitname_3 > component_adminunitname_3a = @Trim(@Value(component_adminunitname_3a),https://geo.data.gov.dk/dataset)
      RENAME_SET_VALUE component_adminunitname_3a > component_adminunitname_3b = @ReplaceString(@Value(component_adminunitname_3b),/,_)
      RENAME_SET_VALUE component_adminunitname_3b > component_adminunitname_3b_# = #_@Value(component_adminunitname_3b_#)
      RENAME_SET_VALUE component_adminunitname_3b_# > component{5}.xlink_href
      REMOVE component_addressareaname_2
      REMOVE component_addressareaname_3
      REMOVE component_adminunitname_4
      REMOVE component_adminunitname_5
      REMOVE component_adminunitname_6
      RENAME_SET_VALUE parentaddress > parentAddress.xsi_nil = true
      SET_TO parentAddress.nilReason = other:unpopulated
      RENAME_SET_VALUE parcel > parcel{0}.xlink_href
      RENAME_SET_VALUE building > building{0}.xlink_href
      RENAME_SET_VALUE gml_location > position{0}.GeographicPosition.geometry
      RENAME_SET_VALUE gmlid > gmlid_a = @Trim(@Value(gmlid_a),https://geo.data.gov.dk/dataset)
      RENAME_SET_VALUE gmlid_a > gml:id = _@ReplaceString(@Value(gml:id),/,_)
      RENAME_SET_VALUE locator_designator_1_designator > locator{0}.AddressLocator.designator{0}.LocatorDesignator.designator
      RENAME_SET_VALUE locator_designator_1_type > locator{0}.AddressLocator.designator{0}.LocatorDesignator.type.xlink_href
      RENAME_SET_VALUE locator_designator_2_designator > locator{0}.AddressLocator.designator{1}.LocatorDesignator.designator
      RENAME_SET_VALUE locator_designator_2_type > locator{0}.AddressLocator.designator{1}.LocatorDesignator.type.xlink_href
      RENAME_SET_VALUE locator_designator_3_designator > locator{0}.AddressLocator.designator{2}.LocatorDesignator.designator
      RENAME_SET_VALUE locator_designator_3_type > locator{0}.AddressLocator.designator{2}.LocatorDesignator.type.xlink_href
      RENAME_SET_VALUE locator_level > locator{0}.AddressLocator.level.xlink_href
      RENAME_SET_VALUE locator_name_name > locator{0}.AddressLocator.name.LocatorName.name.xsi_nil = true
      SET_TO locator{0}.AddressLocator.name.LocatorName.name.nilReason = other:unpopulated
      RENAME_SET_VALUE locator_name_type > locator{0}.AddressLocator.name.LocatorName.type.xsi_nil = true
      SET_TO locator{0}.AddressLocator.name.LocatorName.type.nilReason = other:unpopulated
      RENAME_SET_VALUE locator_withinscopeof_addressareaname > locator{0}.AddressLocator.withinScopeOf.xlink_href
      RENAME_SET_VALUE locator_withinscopeof_adminunitname > locator{0}.AddressLocator.withinScopeOf.xlink_href
      RENAME_SET_VALUE locator_withinscopeof_postaldescriptor > locator{0}.AddressLocator.withinScopeOf.xlink_href
      RENAME_SET_VALUE locator_withinscopeof_thoroughfarename > locator{0}.AddressLocator.withinScopeOf.xlink_href
    -> FeatureWriter [Output02]
Thoroughfarename_GPKG2GML: AttributeManager
    ATTR_TABLE:
      RENAME_SET_VALUE validto > validTo = @DateTimeFormat(@Value(validTo), ISO)
      RENAME_SET_VALUE inspireid > inspireId.Identifier.localId = @TrimLeft(@Value(inspireId.Identifier.localId),https://geo.data.gov.dk/dataset/)
      SET_TO inspireId.Identifier.namespace = https://geo.data.gov.dk/dataset/50b921ea-935e-d605-2287-4ee364046795
      RENAME_SET_VALUE alternativeidentifier > alternativeIdentifier.xsi_nil = true
      SET_TO alternativeIdentifier.nilReason = other:unpopulated
      RENAME_SET_VALUE beginlifespanversion > beginLifespanVersion = @DateTimeFormat(@Value(beginLifespanVersion), ISO)
      RENAME_SET_VALUE endlifespanversion > endLifespanVersion = @DateTimeFormat(@Value(endLifespanVersion), ISO)
      RENAME_SET_VALUE status > status.nilReason
      SET_TO status.xsi_nil = true
      RENAME_SET_VALUE validfrom > validFrom = @DateTimeFormat(@Value(validFrom), ISO)
      RENAME_SET_VALUE name_name > name{0}.ThoroughfareNameValue.name.GeographicalName.spelling{0}.SpellingOfName.text
      SET_TO name{0}.ThoroughfareNameValue.name.GeographicalName.spelling{0}.SpellingOfName.script = Latn
      SET_TO name{0}.ThoroughfareNameValue.name.GeographicalName.language = dan
      RENAME_SET_VALUE transportlink > transportLink{0}.nilReason
      SET_TO transportLink{0}.xsi_nil = true
      REMOVE name_nameparts_part
      REMOVE name_nameparts_type
      RENAME_SET_VALUE situatedwithin_addressareaname > situatedWithin{3}.xlink_href
      RENAME_SET_VALUE situatedwithin_adminunitname > situatedWithin{2}.xlink_href
      RENAME_SET_VALUE situatedwithin_postaldescriptor > situatedWithin{1}.xlink_href
      RENAME_SET_VALUE situatedwithin_thoroughfarename > situatedWithin{0}.nilReason = other:unpopulated
      SET_TO situatedWithin{0}.xsi_nil = true
      RENAME_SET_VALUE gmlid > gmlid_a = @Trim(@Value(gmlid_a),https://geo.data.gov.dk/dataset)
      RENAME_SET_VALUE gmlid_a > gml:id = _@ReplaceString(@Value(gml:id),/,_)
    -> FeatureWriter [Output03]
